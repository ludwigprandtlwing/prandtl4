# -*- coding: utf-8 -*-

place = u'J:/phD/PrandtlVlerk/CAD/'

# Macro Begin: WingModel.FCMacro +++++++++++++++++++++++++++++++++++++++++++++++++
import FreeCAD
import PartDesign
import importAirfoilDAT
import DraftTools
import PartDesignGui
import Part

App.newDocument("Prandtl")
App.setActiveDocument("Prandtl")
App.ActiveDocument=App.getDocument("Prandtl")

sectionstring = place + 'section_01.dat'
importAirfoilDAT.insert(sectionstring,"Prandtl")
import Draft
Draft.scale([App.ActiveDocument.section_01],delta=FreeCAD.Vector(100.0,100.0,1.0),center=FreeCAD.Vector(0.16278848052,0.0274517796934,0.0),copy=False,legacy=True)

#Gui.SendMsgToActiveView("ViewFit")
sectionstring = place + 'section_06.dat'
importAirfoilDAT.insert(sectionstring,"Prandtl")
#Gui.SendMsgToActiveView("ViewFit")
#Gui.ActiveDocument.setEdit('DWire001',0)
App.getDocument("Prandtl").DWire001.Placement=App.Placement(App.Vector(0,0,10), App.Rotation(App.Vector(0,0,1),0), App.Vector(0,0,0))
App.getDocument("Prandtl").DWire001.Placement=App.Placement(App.Vector(0,0,10), App.Rotation(App.Vector(0,0,1),0), App.Vector(0,0,0))
#Gui.ActiveDocument.setEdit('DWire001',0)
App.getDocument("Prandtl").DWire001.Placement=App.Placement(App.Vector(0,0,2), App.Rotation(App.Vector(0,0,1),0), App.Vector(0,0,0))
sectionstring = place + 'section_19.dat'
importAirfoilDAT.insert(sectionstring,"Prandtl")
#Gui.SendMsgToActiveView("ViewFit")
App.getDocument("Prandtl").DWire002.Placement=App.Placement(App.Vector(1,0,3), App.Rotation(App.Vector(0,0,1),0), App.Vector(0,0,0))
App.getDocument("Prandtl").DWire001.Placement=App.Placement(App.Vector(0,0.4,2), App.Rotation(App.Vector(0,0,1),0), App.Vector(0,0,0))
from FreeCAD import Base
App.getDocument('Prandtl').addObject('Part::Loft','Loft')
App.getDocument('Prandtl').ActiveObject.Sections=[App.getDocument('Prandtl').DWire, App.getDocument('Prandtl').DWire001, App.getDocument('Prandtl').DWire002, ]
App.getDocument('Prandtl').ActiveObject.Solid=False
App.getDocument('Prandtl').ActiveObject.Ruled=False
App.getDocument('Prandtl').ActiveObject.Closed=False

# Macro End: WingModel.FCMacro +++++++++++++++++++++++++++++++++++++++++++++++++
